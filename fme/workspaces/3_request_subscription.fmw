FME workspace 3_request_subscription.fmw
Title: none2none

Parameters:
- email = aaron.koning+concert58@safe.com   # " " Email address to subscribe
- topic = concert_communications   # " " Topic to subscribe to
- wkt = POLYGON ((127.65 26.09,127.81 26.16,140.39 35.17,140.84 35.74,145.81 43.37,145.34 44.34,141.97 45.49,141.69 45.4,129.3 34.56,128.65 32.7,127.65 26.09))   # Area to subscribe to (WKT)

Writers:
- POSTGIS_1: POSTGIS to demo
- TEXTLINE_1: TEXTLINE to /Users/akoning/Google Drive/Projects/subscribing/output/email.txt

Creator
    NUM = 1
    GEOMTYPE = Geometry Object
    CREATED -> GeometryReplacer
GeometryReplacer
    SOURCE = $(wkt)
    REMOVE_ATTRIBUTE = No
    KIND_LONG = OGC Well Known Text
    -> CoordinateSystemSetter
CoordinateSystemSetter
    COORDSYS = EPSG:4326
    -> AttributeCreator
AttributeCreator
    ATTR_LIST = email_address,$(email),topic_name,$(topic)
    -> UUIDGenerator
UUIDGenerator
    UUID_ATTR = confirm_token
    -> subscription_request_database (writer POSTGIS_1)
    -> FMEServerEmailGenerator
subscription_request_database (writer POSTGIS_1)
    attributes: email_address char(50), topic_name char(30), confirm_token char(40)
FMEServerEmailGenerator
    email_subject = Confirm subscription - required
    email_to = $(email)
    email_subscriber_content:
      <p>We received a request for $(email) to be subscribed to the $(topic) topic. You need to confirm this subscription before we activate it.<p>
      <p><a href="https://bluesky-safe-software.fmecloud.com/fmedatastreaming/notification_tutorial/3_confirm_subscription.fmw?confirm_token=@Value(confirm_token)">Click this link to confirm the subscription</a></p>
    -> text_line (writer TEXTLINE_1)
text_line (writer TEXTLINE_1)
    attributes: text_line_data buffer

FME custom transformer FMEServerEmailGenerator
This transformer provides an easy method for creating an email message to be sent by the FME Server Notification Service.
1. Create Topic and Email Subscriber
In the FME Server Web Interface, create a topic for notifications to be sent to and also create a email subscriber that subscribes to this topic.
2. Create a Workspace 
Once you file out the the email fields in the transformer you can send the email message in two different ways:
A. Send an email when the workspace completes
add a text file writer to the workspace
connect this transformer to the text file writer's feature type
publish the workspace
register it with the Job Submitter, Data Download and/or Notification Service
for each service, click the edit button
for Topics to Publish (Success), select the topic you created earlier
for Notification Writer, select the text file writer you added eariler
finish publishing the workspace
now the workspace will send an email whenever it is run through the FME Server Service you registered it with.
B. Send an email using a transformer
add a FMEServerNotifier transformer to your workflow
configure it to publish to the topic that you created earlier
for Content, select the text_line_data attribute
now the workspace will send an email whenever it is run.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_to =   # To
- email_cc =   # CC
- email_from =   # From
- email_replyto =   # Reply to
- email_subject =   # Subject
- email_subscriber_content =   # Message
- email_attachment_paths =   # Attachments (comma separated)

INPUT (input)
    -> Counter
Counter
    SCOPE = Local
    START = 0
    DOMAIN = counter
    CNT_ATTR = _email_feature_id
    -> ParameterFetcher
ParameterFetcher
    ATTR_LIST = _email_from {$(email_from)} _email_replyto {$(email_replyto)} _email_attachment_paths {$(email_attachment_paths)} _email_cc {$(email_cc)}
    -> AttributeCreator
AttributeCreator
    NUM_PRIOR_FEATURES = 0
    NUM_SUBSEQUENT_FEATURES = 0
    ATTR_LIST = _email_to,$(email_to),_email_subject,$(email_subject),_email_subscriber_content,$(email_subscriber_content)
    -> JSONTemplater
JSONTemplater
    RESULT_ATTRIBUTE = text_line_data
    CONSECUTIVE_GROUPS = No
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    VISIBLE_QUERY_VALIDATE = Yes
    -> Tester
Tester
    TEST_MODE = Automatic
    TEST_DESCRIPTION = ""
    BOOL_OP = OR
    TEST_CLAUSE = TEST _email_attachment_paths ATTRIBUTE_IS_EMPTY <Unused>
    PASSED -> OUTPUT (output)
    FAILED -> AttributeSplitter
OUTPUT (output)

Bookmark: Add the attachments
AttributeSplitter
    LIST_NAME = _email_attachment_path_list
    ATTR_NAME = _email_attachment_paths
    DELIMITER = ,
    TRIM_OPTION = Both
    DROP_EMPTY_PARTS = No
    -> ListExploder
ListExploder
    INDEX_ATTR = _element_index
    MODE = List Elements and Original Attributes
    LIST_ATTR = _email_attachment_path_list{}
    LIST_FOUND -> StringConcatenator
StringConcatenator
    PARM_LINE = "email_attachment{@Value(_element_index)}": "@Value(_email_attachment_path_list)"
    VAL_ATTR = _email_attachment_json
    -> Aggregator
Aggregator
    GROUP_BY = _email_feature_id
    MODE = Assemble One Level
    ACCUM_ATTRS_NAME = Yes
    SEP = ,
    AGGREGATE_TYPE = Homogeneous Collection (If Possible)
    CONCAT_ATTRS = _email_attachment_json
    ORDERED = No
    AGGREGATE -> StringReplacer_2
StringReplacer_2
    SRC_ATTRS = _email_attachment_json
    REGEXP = no
    CASE = no
    REPLACE_TEXT = \\
    NO_MATCH = _FME_NO_OP_
    FIND_TEXT = \
    -> StringReplacer
StringReplacer
    SRC_ATTRS = text_line_data
    REGEXP = no
    CASE = no
    REPLACE_TEXT:
      ,
      @Value(_email_attachment_json)
      }
    NO_MATCH = _FME_NO_OP_
    FIND_TEXT = }
    -> OUTPUT (output)
