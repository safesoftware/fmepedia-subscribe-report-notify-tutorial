FME workspace 3_create_subscription_database.fmw

Parameters:
- SourceDataset_SPATIALITE = /Users/akoning/Google Drive/FME Server/Knowledge Base/2014/subscribe, report, notify tutorial/data/continents.sl3   # Source SpatiaLite Database File(s)
- DestDataset_POSTGIS = demo   # Destination PostGIS Dataset

Readers:
- SPATIALITE_1: SPATIALITE from $(SourceDataset_SPATIALITE)

Writers:
- POSTGIS_1: POSTGIS to $(DestDataset_POSTGIS)

continents (reader SPATIALITE_1)
    attributes: continent string(255)
    -> AttributeFilter
AttributeFilter
    ATTR_NAME = continent
    ATTR_VALUES = <EMPTY>,<MISSING>,<NULL>,<UNFILTERED>,South America,North America,Europe
    South America -> AttributeCreator
    Europe -> AttributeCreator_3
    North America -> AttributeCreator_2
AttributeCreator
    ATTR_LIST = email_address,aaron.koning+nature@safe.com,topic_name,nature_news
    -> UUIDGenerator
AttributeCreator_2
    ATTR_LIST = email_address,aaron.koning+transit@safe.com,topic_name,transit_tips
    -> UUIDGenerator
AttributeCreator_3
    ATTR_LIST = email_address,aaron.koning+concert@safe.com,topic_name,concert_communications
    -> UUIDGenerator
UUIDGenerator
    UUID_ATTR = confirm_token
    -> subscription_database (writer POSTGIS_1)
    -> subscription_request_database (writer POSTGIS_1)
subscription_database (writer POSTGIS_1)
    attributes: email_address char(50), topic_name char(30), confirm_token char(40)
subscription_request_database (writer POSTGIS_1)
    attributes: email_address char(50), topic_name char(30), confirm_token char(40)
