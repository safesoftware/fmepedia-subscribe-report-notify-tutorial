FME workspace 3_confirm_subscription.fmw
Title: none2none

Parameters:
- confirm_token = cd0f8d0e-0d67-11e4-8a21-e35d27   # Confirm Token

Writers:
- TEXTLINE_1: TEXTLINE to /Users/akoning/Google Drive/FME Server/Knowledge Base/2014/subscribe, report, notify tutorial/output/output.txt
- POSTGIS_2: POSTGIS to demo

Creator
    NUM = 1
    GEOMTYPE = Geometry Object
    CREATED -> ParameterFetcher
ParameterFetcher
    ATTR_LIST = _confirm_token {$(confirm_token)}
    -> FeatureReader
FeatureReader
    WHERE = confirm_token = '@Value(_confirm_token)'
    FEATURETYPES = public.subscription_request_database
    POSTGIS_HOST = demo.cicwnprtlhsw.us-east-1.rds.amazonaws.com
    COMBINE_GEOM = Keep result geometry only
    POSTGIS_TABLELIST = public.subscription_request_database
    POSTGIS_USER_NAME = demo
    POSTGIS_PASSWORD =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
    COMBINE_ATTRS = In case of conflict, keep result attributes
    POSTGIS_USE_TRUE_POSTGIS_TYPES = yes
    POSTGIS_PORT = 5432
    SUPPORTED_SPATIAL_INTERACTIONS = ENVELOPE_INTERSECT%ENVELOPE_INTERSECT%INTERSECTS%CONTAINS%CROSSES%DISJOINT%EQUALS%OVERLAPS%TOUCHES%WITHIN
    DATASET = demo
    ATTRIBUTES = public.subscription_request_database,"email_address,topic_name,confirm_token"
    POSTGIS_DISABLE_COLLECTION_SPLITTING = yes
    FORMAT = POSTGIS
    public.subscription_request_database -> DatabaseDeleter
    public.subscription_request_database -> AttributeCreator
    public.subscription_request_database -> subscription_database (writer POSTGIS_2)
subscription_database (writer POSTGIS_2)
    attributes: email_address char(50), topic_name char(30), confirm_token char(30)
DatabaseDeleter
    POSTGIS_PORT = 5432
    TABLE = public.subscription_request_database
    MATCH_COLUMNS = confirm_token;@Value(_confirm_token)
    POSTGIS_USER_NAME = demo
    DATASET = demo
    CONDITION = Match Column(s)
    POSTGIS_HOST = demo.cicwnprtlhsw.us-east-1.rds.amazonaws.com
    POSTGIS_PASSWORD =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
    FORMAT = POSTGIS
AttributeCreator
    ATTR_LIST = text_line_data,<p>@Value(email_address) subscription to @Value(topic_name) topic has been activated. <p>
    -> text_line (writer TEXTLINE_1)
text_line (writer TEXTLINE_1)
    attributes: text_line_data buffer
